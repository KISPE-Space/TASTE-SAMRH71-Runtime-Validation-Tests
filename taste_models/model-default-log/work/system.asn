-- Dataview generated on-the-fly providing information on the system
-- and made available to the user code.
System-Dataview DEFINITIONS ::=
BEGIN

   -- Range of PID - type can be used to size arrays of PID type
   PID-Range ::= INTEGER(0..7)

   -- List of functions (instances) present in the system
   PID ::= ENUMERATED {
       tf-reporter,
       
       uartotherend,
       
       log-flooder,
       
       receiver,
       
       test-log-length,
       
       test-logging,
       
       trigger-logging,
       
       
       env
   }

END
