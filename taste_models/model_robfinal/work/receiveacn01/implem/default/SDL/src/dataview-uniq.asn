MODEL-TF1-DATAVIEW DEFINITIONS ::=
BEGIN

   MyInteger ::= INTEGER (0 .. 10000)

-- ASN.1 Type definitions must start with an uppercase
-- Field names in records (SEQUENCE) must start with a lowercase
-- Underscores are not allowed: use dash (hyphen) 
-- For integers do not assume that small ranges will be translated to small
-- types in C or Ada (expect unsigned or signed 64 bits types with subtypes
-- for the range in Ada)

-- Simple types:

-- TASTE-Boolean ::= BOOLEAN
-- MyInteger   ::= INTEGER (0..255)
-- MyReal      ::= REAL (0.0 .. 1000.0)
-- MyBool      ::= BOOLEAN
-- MyEnum      ::= ENUMERATED { hello, world, how-are-you }

-- Complex types:

--  MySeq       ::= SEQUENCE {
--      input-data  MyInteger,
--      output-data MyInteger,
--      validity    ENUMERATED { valid, invalid }
--  }
--
--  MyChoice    ::= CHOICE {
--      a BOOLEAN,
--      b MySeq
--  }
--
--  MySeqOf     ::= SEQUENCE (SIZE (2)) OF MyEnum
--
--  MyOctStr    ::= OCTET STRING (SIZE (3))
--
--  -- You can also declare constants
--  myVar       MySeqOf     ::= { hello, world }

    Counter :: ::= INTEGER (0 .. 10000)

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

T-Runtime-Error ::= CHOICE {
   noerror T-UInt32, -- this shall be NULL, but DMT does not support NULL and SEDS does not support empty sequences
   encodeerror T-Int32, -- the names shall be changed after fix in seds converter (space creator) will be merged
   decodeerror T-Int32
}

END

-- Dataview generated on-the-fly providing information on the system
-- and made available to the user code.
System-Dataview DEFINITIONS ::=
BEGIN

   -- Range of PID - type can be used to size arrays of PID type
   PID-Range ::= INTEGER(0..89)

   -- List of functions (instances) present in the system
   PID ::= ENUMERATED {
       boothelper00f,
       
       brokerlock00g,
       
       brokertest002a,
       
       deathreport00c,
       
       escapertest002b,
       
       faulthandler00b,
       
       function-1,
       
       function-10,
       
       function-11,
       
       function-12,
       
       function-13,
       
       function-14,
       
       function-15,
       
       function-16,
       
       function-17,
       
       function-18,
       
       function-19,
       
       function-2,
       
       function-20,
       
       function-21,
       
       function-22,
       
       function-23,
       
       function-24,
       
       function-25,
       
       function-26,
       
       function-27,
       
       function-28,
       
       function-29,
       
       function-3,
       
       function-30,
       
       function-31,
       
       function-32,
       
       function-33,
       
       function-34,
       
       function-35,
       
       function-36,
       
       function-37,
       
       function-38,
       
       function-39,
       
       function-4,
       
       function-40,
       
       function-41,
       
       function-42,
       
       function-43,
       
       function-44,
       
       function-45,
       
       function-46,
       
       function-47,
       
       function-48,
       
       function-5,
       
       function-6,
       
       function-7,
       
       function-8,
       
       function-9,
       
       hal00d,
       
       mqueuecallback12,
       
       monitoring00a,
       
       paketizer002c,
       
       receiveacn,
       
       receiver001,
       
       receiver011,
       
       receiver012,
       
       receiver013,
       
       receiver014,
       
       receiver015,
       
       receiver016,
       
       receiver017,
       
       receiver018,
       
       receiver019,
       
       receiver020,
       
       samrh71core00h,
       
       sendacn,
       
       sender001,
       
       sender002,
       
       sender003,
       
       sender004,
       
       sender006,
       
       sender007,
       
       sender008,
       
       sender009,
       
       sender010,
       
       sender011,
       
       sernder005,
       
       testcyclic05,
       
       testmsgsp03,
       
       testmsgup04,
       
       testsdl08,
       
       teststart00,
       
       threads00e,
       
       
       env
   }

END
