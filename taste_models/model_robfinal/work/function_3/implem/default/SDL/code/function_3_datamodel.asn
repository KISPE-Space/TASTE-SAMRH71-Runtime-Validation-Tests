Function-3-Datamodel DEFINITIONS ::=
BEGIN
--  This file was generated automatically by OpenGEODE
IMPORTS
   MyInteger FROM MODEL-TF1-DATAVIEW
   T-Int32, T-UInt32, T-Int8, T-UInt8, T-Boolean, T-Null-Record, T-Runtime-Error FROM TASTE-BasicTypes
   PID-Range, PID FROM System-Dataview;

Function-3-States ::= ENUMERATED {wait}

Function-3-Context ::= SEQUENCE {
   state Function-3-States,
   init-done BOOLEAN,
   sender PID,
   offspring PID
}

Function-3-T-Runtime-Error-Selection ::= ENUMERATED {noerror-present(1), encodeerror-present(2), decodeerror-present(3)}
END
