Sdl-timer-Datamodel DEFINITIONS ::=
BEGIN
--  This file was generated automatically by OpenGEODE
IMPORTS
   MyInteger FROM MODEL-SDL-TO-ADA-DATAVIEW
   T-Int32, T-UInt32, T-Int8, T-UInt8, T-Boolean, T-Null-Record, T-Runtime-Error FROM TASTE-BasicTypes
   PID-Range, PID FROM System-Dataview;

Sdl-timer-States ::= ENUMERATED {wait}

Sdl-timer-Context ::= SEQUENCE {
   state Sdl-timer-States,
   init-done BOOLEAN,
   sender PID,
   offspring PID,
   tick-time MyInteger,
   counter MyInteger
}

Sdl-Timer-T-Runtime-Error-Selection ::= ENUMERATED {noerror-present(1), encodeerror-present(2), decodeerror-present(3)}
END
