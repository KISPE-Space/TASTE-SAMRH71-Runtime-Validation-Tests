-- Dataview generated on-the-fly providing information on the system
-- and made available to the user code.
System-Dataview DEFINITIONS ::=
BEGIN

   -- Range of PID - type can be used to size arrays of PID type
   PID-Range ::= INTEGER(0..77)

   -- List of functions (instances) present in the system
   PID ::= ENUMERATED {
       activationlog,
       boothelper00f,
       brokerlock00g,
       brokertest002a,
       deathreport00c,
       escapertest002b,
       function-1,
       function-10,
       function-11,
       function-12,
       function-13,
       function-14,
       function-15,
       function-16,
       function-17,
       function-18,
       function-19,
       function-2,
       function-20,
       function-21,
       function-22,
       function-23,
       function-24,
       function-3,
       function-4,
       function-5,
       function-6,
       function-7,
       function-8,
       function-9,
       hal00d,
       mqueuecallback12,
       monitorcallback,
       monitoring00a,
       paketizer002c,
       prot00if,
       prot05ifin,
       prot05ifout,
       rcvacn01,
       rcvacn02,
       rcvacn03,
       rcvacn04,
       receiver001,
       receiver011,
       receiver012,
       receiver013,
       receiver014,
       receiver015,
       receiver016,
       receiver017,
       receiver018,
       receiver019,
       receiver020,
       samrh71core00h,
       sendacn,
       sender001,
       sender002,
       sender003,
       sender004,
       sender006,
       sender007,
       sender008,
       sender009,
       sender010,
       sender011,
       sernder005,
       testcyclic05,
       testprotected,
       testsdl08,
       testsdl14,
       teststart00,
       testunprot00,
       testunprotin05,
       testunprotout05,
       testunprotected,
       threads00e,
       rcvacn05,
       
       env
   }

END
